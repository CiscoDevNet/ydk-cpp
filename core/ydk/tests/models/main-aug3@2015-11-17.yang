module main-aug3 {

  /*** NAMESPACE / PREFIX DEFINITION ***/

  namespace "http://cisco.com/ns/yang/main-aug3";


  prefix "aug3";

  /*** LINKAGE (IMPORTS / INCLUDES) ***/
  import main { prefix "main"; }


  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for sanity package.

     This module contains definitions
     for the following management objects:


     Copyright (c) 2013-2014 by Cisco Systems, Inc.
     All rights reserved.";

  revision "2015-11-17" {
    description
      "Initial revision.";
  }

  augment /main:A {
    container C {

      leaf meh {
        description "blah";
        type int8;
      }
    }


    container D {

      leaf buh {
        description "blah";
        type string;
      }
    }
  }
}
