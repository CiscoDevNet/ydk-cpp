module main-aug2 {

  /*** NAMESPACE / PREFIX DEFINITION ***/

  namespace "http://cisco.com/ns/yang/main-aug2";

  prefix "aug2";

  /*** LINKAGE (IMPORTS / INCLUDES) ***/
  import main { prefix "main"; }


  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for sanity package.

     This module contains definitions
     for the following management objects:


     Copyright (c) 2013-2014 by Cisco Systems, Inc.
     All rights reserved.";

  revision "2015-11-17" {
    description
      "Initial revision.";
  }

  augment /main:A {
    container C {

      leaf three {
        description "blah";
        type int16;
      }
    }

    container D {

      leaf poo {
        description "blah";
        type int32;
      }
    }
  }
}
