module ydktest-sanity-action {
  yang-version 1.1;

  /*** NAMESPACE / PREFIX DEFINITION ***/

  namespace "http://cisco.com/ns/yang/ydktest-action";


  prefix "ydk-a";

  /*** LINKAGE (IMPORTS / INCLUDES) ***/

  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for sanity package.

     This module contains definitions
     for the following management objects:

     Copyright (c) 2013-2014 by Cisco Systems, Inc.
     All rights reserved.";

  revision "2018-03-17" {
    description
      "Initial revision.";
  }

  container data {
    action action-node {
        input {
            leaf test {
                type string;
            }
        }
        output {
            leaf t {
                type string;
            }
        }
    }
  }

  rpc transaction {
    description
      "Transaction RPC";
    input {
      container run-request {
        leaf out-format {
          type string;
        }
      }
    }
    output {
      container run-result {
        leaf out-result {
          type string;
        }
      }
    }
  }
}
