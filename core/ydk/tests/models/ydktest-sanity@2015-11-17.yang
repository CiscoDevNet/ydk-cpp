module ydktest-sanity {

  /*** NAMESPACE / PREFIX DEFINITION ***/

  namespace "http://cisco.com/ns/yang/ydktest-sanity";


  prefix "ydkut";

  /*** LINKAGE (IMPORTS / INCLUDES) ***/

  //import ietf-inet-types { prefix "inet"; }

  import ydktest-types { prefix "types"; }

  include ydktest-sanity-submodule {
    revision-date 2016-04-25;
  }

  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for sanity package.

     This module contains definitions
     for the following management objects:

     Copyright (c) 2013-2014 by Cisco Systems, Inc.
     All rights reserved.";

  revision "2015-11-17" {
    description
      "Initial revision.";
  }

 identity base-identity;

 identity child-identity {
   base base-identity;
  }

  identity child-child-identity {
     base child-identity;
  }

 typedef Ydk-Enum-test {
    type enumeration {
      enum not-set {
        value 0;
        description "Not Set";
      }
      enum none {
        value 1;
        description "None";
      }
      enum local {
        value 2;
        description "Local";
      }
      enum remote {
        value 3;
        description "Remote";
      }
    }
    description "YDK Enum test";
  }

  typedef Ydk-Enum-Int-test {
    type union {
      type enumeration {
        enum any {
          value 4096;
          description "Any value";
        }
      }
      type uint32 {
        range "1..4096";
      }
    }
    description "Int or any";
  }

  grouping leaf-ref-g {
    description "testing for leaf-ref";
    container leaf-ref {
      leaf ref-one-name {
        type leafref {
          path "/runner/one/name";
        }
      }
      leaf ref-two-sub1-number {
        type leafref {
          path "/runner/two/sub1/number";
        }
      }
      leaf ref-three-sub1-sub2-number {
        type leafref {
          path "/runner/three/sub1/sub2/number";
        }
      }
      leaf ref-inbtw {
        type leafref {
          path "/runner/inbtw-list/ldata[number = current()/../ref-two-sub1-number]"
            + "/subc/subc-subl1[number = current()/../ref-three-sub1-sub2-number]/name";
        }
      }
      container one {
        leaf name-of-one {
          type string {
            pattern '(([0-9]|[1-9][0-9]|1[0-9][0-9]|2[0-4][0-9]|25[0-5])\.){3}([0-9]|[1-9][0-9]|1[0-9][0-9]|2[0-4][0-9]|25[0-5])(%[\p{N}\p{L}]+)?';
          }

        }
        container two {
          leaf self-ref-one-name {
            type leafref {
              path "../../../ref-one-name";
            }
          }
        }
      }
    }
  }

  grouping one-level {
    description "testing for couple of leaves";
    container one {
      description "config for one_level data";
      leaf number {
        description "integer value type";
        type int32;
      }

      leaf name {
        description "this is string value";
        type string;
      }
      anyxml config {
          description "test";
      }
    }
  }

  grouping two-level {
    description "testing for couple of leaves";
    container two {
      description "config for one_level data";
      leaf number {
        description "integer value type";
        type int32;
      }

      leaf name {
        description "this is string value";
        type string;
      }

      container sub1 {
        description "subconfig1 for config container";
        leaf number {
          description "integer value type";
          type int32;
        }
      }
    }
  }

  grouping three-level {
    description "testing for couple of leaves";
    container three {
      description "config for one_level data";
      leaf number {
        description "integer value type";
        type int32;
      }

      leaf name {
        description "this is string value";
        type string;
      }

      container sub1 {
        description "subconfig1 for config container";
        leaf number {
          description "integer value type";
          type int32;
        }

        container sub2 {
          description "subconfig2 for config container";
          leaf number {
            description "integer value type";
            type int32;
          }
        }
      }
    }
  }

  grouping all-ytypes-class {
    description "testing for couple of leaves";
    container ytypes {
      container none {
        leaf test {
            type string;
        }
      }
    
      description "config for one_level data types";
      leaf enabled {
        type empty;
      }
      container built-in-t {
        description "config for built-in types";

        leaf number8 {
          description " 8 bit integer value type";
          type int8;
        }

        leaf number16 {
          description "16 bit integer value type";
          type int16;
        }

        leaf number32 {
          description "integer value type";
          type int32 {
            range "min..0 | 10 | 19 | 1000..max";
          }
        }

        leaf number64 {
          description "integer value type";
          type int64;
        }

        leaf u_number8 {
          description " 8 bit uinteger value type, must be >=0 & <= 255";
          type uint8;
        }

        leaf u_number16 {
          description "16 bit uinteger value type, must be >=0 & <= 65025";
          type uint16;
        }

        leaf u_number32 {
          description "32 bit uinteger value type";
          type uint32;
        }

        leaf u_number64 {
          description "64 bit uinteger value type";
          type uint64;
        }
        leaf leaf-ref {
          description "leaf-ref";
          type leafref {
            path "/runner/ytypes/built-in-t/number8";
          }
        }


        leaf deci64 {
          description "this is decimal value";
          type decimal64 {
            fraction-digits 2;
            range "1 .. 3.14 | 10 | 20..max";
          }
        }


        leaf name {
          description "this is string value";
          type string;
        }

        leaf emptee {
          description "this is empty value";
          type empty;
        }

        leaf bool-value {
          description "this is boolean type value";
          type boolean;
        }

        leaf embeded-enum {
          description "enum embeded in leaf";
          type enumeration {
            enum zero;
            enum two;
            enum seven {
              value 7;
            }
          }
        }

        leaf enum-leafref {
            type leafref {
                path "../embeded-enum";
            }
        }

        leaf enum-value {
          description "this is enum type value";
          type Ydk-Enum-test;
        }

        leaf enum-int-value {
            description "enum int type";
            type Ydk-Enum-Int-test;
        }

        leaf identity-ref-value {
          type identityref {
            base base-identity;
           }
        }

        leaf bincoded {
          description "this is binary value";
          type binary;
        }

        leaf bits-value {
          description "this is bits type value";
          type types:Ydk-bits-type;
          default "auto-sense-speed";
        }
        
        //TODO
        /*leaf-list bits-list {
          description "this is bits type list";
          type bits {
            bit val1 {
              position 0;
            }

            bit val2 {
              position 1;
            }
          }
        }*/

        leaf younion {
          type union {
            type Ydk-Enum-test;
            type uint32 {
              range "0..63";
            }
          }
          description "union test value";
        }
        //enhance identity, instance-identifier, decimal-64

        //leaf-list types for all types
        leaf-list llstring {
          type string;
          description "A list of string";
        }

        leaf status {
            description
              "Whether cable is connected or not";
            type enumeration {
              enum "good";
              enum "not connected";
            }
          }

        leaf-list bits-llist {
          type bits {
            bit disable-nagle {
              position 0;
            }

            bit auto-sense-speed {
              position 1;
            }
          }
        }

        leaf-list enum-llist {
          type Ydk-Enum-test;
          description "A leaf-list of enum";
          max-elements 3;
        }

        leaf-list identity-llist {
          type identityref {
            base base-identity;
           }
          description "A leaf-list of identityref";
        }

        leaf-list llunion {
          type union {
              type int16;
              type string;
          }
          description "A list of union";
        }

        leaf younion-recursive {
            type types:Ydk-Recursive-Union-type;
            description "Recursive union leaf";
        }

        leaf-list younion-list {
             type union {
                type types:Ydk-Simple-Union-type;
                type types:Ydk-String-type;
                type string;
                //type types:Ydk-Identity-type; //TODO this does not work
              }
              description
                "members of the younion";
        }


        //leaf-refs refeerring to different target node


        //Other convoluted test case
        //submodule definitions
        // imports from other modules

        // identityref
        // instance-indentifier
        //
      }

      container derived-t {
        description "config for one_level derived data types";

      }
    }
  }

  grouping one-level-w-list {
    container one-list {
      description "config for one_level list data";
      list ldata {
        description "one list data";
        key "number";
        max-elements 5;
        leaf number {
          description "integer value type";
          type int32;
        }

        leaf name {
          description "this is string value";
          type string;
        }
      }

      list identity-list {
        description "one list data";
        key "id-ref";
        max-elements 5;
        leaf id-ref {
          description "leafref key";
          type leafref {
            path "../config/id";
          }
        }

        container config {
          leaf id{
            description "base id id ref";
            type identityref {
              base base-identity;
            }
          }
        }
      }
    }
  }

  grouping two-level-w-list {
    container two-list {
      description "config for one_level list data";
      list ldata {
        description "one list data";
        key "number";
        leaf number {
          description "integer value type";
          type int32;
        }

        leaf name {
          description "this is string value";
          type string;
        }

        list subl1 {
          description "one list data";
          key "number";
          leaf number {
            description "integer value type";
            type int32;
          }

          leaf name {
            description "this is string value";
            type string;
          }
        }
      }
    }
  }

  grouping three-level-w-list {
    container three-list {
      description "config for one_level list data";
      list ldata {
        description "one list data";
        key "number";
        leaf number {
          description "integer value type";
          type int32;
        }

        leaf name {
          description "this is string value";
          type string;
        }

        list subl1 {
          description "one list data";
          key "number";
          leaf number {
            description "integer value type";
            type int32;
          }

          leaf name {
            description "this is string value";
            type string;
          }

          list sub-subl1 {
            description "one list data";
            key "number";
            leaf number {
              description "integer value type";
              type int32;
            }

            leaf name {
              description "this is string value";
              type string;
            }
          }
        }
      }
    }
  }

  grouping three-level-w-list-at-two {
    container inbtw-list {
      description "config for one_level list data";
      list ldata {
        description "one list data";
        key "number";
        leaf number {
          description "integer value type";
          type int32;
        }

        leaf name {
          description "this is string value";
          type string;
        }

        container subc {
          description "one list subcontainer data";
          leaf number {
            description "integer value type";
            type int32;
          }

          leaf name {
            description "this is string value";
            type string;
          }

          list subc-subl1 {
            description "one list data";
            key "number";
            leaf number {
              description "integer value type";
              type int32;
            }

            leaf name {
              description "this is string value";
              type string;
            }
          }
        }
      }
    }
  }

  grouping not-supported {
    container not-supported-1 {
      container not-supported-1-2 {
        leaf some-leaf {
          type string;
        }
      }
      leaf not-supported-leaf {
        type string;
      }
    }
    list not-supported-2 {
      key "number";
      leaf number {
        description "Integer key for not supported list";
        type int32;
      }
    }
  }

  grouping nested-naming {
    container nested-naming {
      container nested-naming {
        container nested-naming {
          leaf nested-naming {
            type int32;
          }
        }
      }
    }
  }

  grouping two-key-list {
    list two-key-list {
        key "first second";
        leaf first {
            type string;
        }
        leaf second {
            type uint32;
        }
        leaf property {
            type string;
        }
    }
  }

  grouping identity-list {
    list identity-list {
        key "name";
        leaf name {
            type identityref {
                base base-identity;
           }
        }
    }
  }

  grouping enum-list {
    list enum-list {
        key "name";
        leaf name {
            type Ydk-Enum-test;
        }
    }
  }

  grouping inner-pres {
    container outer {
        container inner {
            presence true;
        }
    }
  }

  grouping one-read-only {
    description "testing for couple of leaves";
    container one-read-only {
      config false;
      description "one_read_only data";
      leaf number {
        description "integer value type";
        type int32;
      }

      leaf name {
        description "this is string value";
        type string;
      }
      anyxml config {
          description "test";
      }
    }
  }

  grouping mtus {
      container mtus {
        list mtu {
            key "owner";

            leaf owner {
                type string;
            }

            leaf mtu {
                type int32 {
                    range "10..8000";
                }
                mandatory true;
            }
        }
    }
  }

  grouping passive {
    list passive {
        key "name";
        leaf name {
            type string;
        }
        list interfac {
            key "test";

            leaf test {
                type string;
            }
        }
    }
  }


  container runner {

    // uses nested-naming;

    //container at 1,2,3 nested level
    uses one-level;
    uses two-level;
    uses three-level;

    //all yang types coverage
    uses all-ytypes-class;

    //list level cases
    uses one-level-w-list;
    uses two-level-w-list;
    uses three-level-w-list;

    uses three-level-w-list-at-two;

    uses two-key-list;

    uses identity-list;

    uses enum-list;

    uses leaf-ref-g;

    uses not-supported;

    uses one-read-only;

    uses mtus;

    uses passive;

    uses inner-pres;

    container runner-2 {
       presence "Runner-2 is presence controlled";
       leaf some-leaf {
          type string;
       }
    }

    list no-key-list {
        config false;
        leaf test {
            type string;
        }
    }

    list one-key-list {
        key testy;
        leaf testy {
            type string;
        }
        container test {
          container best {
            leaf gest {
                type string;
            }
          }
        }
    }

    list mand-list {
        key "name";
        leaf name {
            type string;
        }
        leaf num {
            type int16;
            mandatory true;
        }
    }
  }
  
  container native {

    leaf version {
      description "Version";
      type string;
    }

    leaf hostname {
      description "Set system's network name";
      type string;
    }

    uses config-interface-grouping;

  } // native

  typedef comp_InstType {
      type enumeration {
          enum unknown {
              value 0;   // Unknown
          }
          enum phys {
              value 1;     // Baremetal Host
          }
          enum virt {
              value 2;     // Virtual Machine
          }
          enum hv {
              value 3;   // Hypervisor Host
          }
      }
      default "unknown";
  }

  typedef comp_NicInstType {
      type comp_InstType;
  }

  container cascading-types {

    leaf comp_InstType {
      description "this is enum type value";
      type comp_InstType;
    }

    leaf comp_NicInstType {
      description "this is enum type value";
      type comp_NicInstType;
    }
  }

  container conditional-interface {
    leaf ifType {
        type enumeration {
            enum ethernet;
            enum atm;
            enum ds0;
        }
    }
    leaf ifMTU {
        type uint32;
    }
    must "(ifType != 'ethernet' and ifType != 'atm') or " +
         "(ifType = 'ethernet' and ifMTU = 1500)" {
        error-message "An ethernet MTU must be 1500";
    }
    must "(ifType != 'atm' and ifType != 'ethernet') or " +
         "(ifType = 'atm' and ifMTU <= 17966 and ifMTU >= 64)" {
        error-message "An atm MTU must be  64 .. 17966";
    }

    when "/conditional-interface/ifType='ds0'";
    leaf ds0ChannelNumber {
      type uint16;
    }
  }

}
